FME workspace ParcelID_Extraction.fmw

Parameters:
- SourceTXT = \\10.10.30.59\gis\ParcelHandling\Data\LEGDAT.txt   # Source Text File
- SourceDataset_GEODATABASE_FILE = \\10.10.30.59\gis\Data\Production.gdb   # File Geodatabase
- DestDataset_GEODATABASE_FILE_2 = \\10.10.30.59\gis\Data\Production.gdb   # File Geodatabase
- SourceDataset_GEODATABASE_FILE_3 = \\10.10.30.59\gis\Data\Production.gdb   # File Geodatabase
- SourceDataset_CSV2 = C:\Users\BrunoBlanco\Desktop\Building Footprints\865_buildings.csv   # Source CSV (Comma Separated Value) File(s)

Readers:
- TEXTLINE_1: TEXTLINE from $(SourceTXT)
- GEODATABASE_FILE_2: GEODATABASE_FILE from $(SourceDataset_GEODATABASE_FILE)
- GEODATABASE_FILE_4: GEODATABASE_FILE from $(SourceDataset_GEODATABASE_FILE_3)
- CSV2_1: CSV2 from $(SourceDataset_CSV2)

Writers:
- GEODATABASE_FILE_3: GEODATABASE_FILE to $(DestDataset_GEODATABASE_FILE_2)

Note: Import both parcel GIS files and the LEGDAT text file provided by the assessor's office. Prep the data from both sources, and then do a match based on a common attribute (parcel ID), then override existing subd names from the GIS parcels with the ones sent in the text file
Note: Parcel ID C0243 00656 is not making it through. It's not getting joined
Note: parAddress needs to be populated / Assign a weighted metrix based on the structure type field with the value 1 = house being the highest
Note: Import source data. Looking for comma delimited text file sent by the assessor's office
text_line (reader TEXTLINE_1)
    attributes: text_line_data buffer
    -> Subd_Name_Replacement
Note: Finds erratic strings in subdivision names and replaces them with standardized versions. / Example: / PHS 1 --> PHASE 1
Subd_Name_Replacement: Subd Name Replacement
    TEXT_LINE_DATA = @Value(text_line_data)
    -> Subd_Name_Cleaners
Note: Then use regex expressions to remove unnecessary parts of subdivision names. / Example: / PHASE 1 --> [nothing]
Subd_Name_Cleaners: Subd Name Cleaners
    TEXT_LINE_DATA = @Value(text_line_data)
    _SUBDNAME = @Value(_SubdName)
    -> Title_Case
Note: Finally, convert subdivision names to Full Title Case
Title_Case: Title Case
    _SUBDNAME = @Value(_SubdName)
    -> Join_Parcels [RIGHT]
Note: Import parcels from GDB
MapData/Parcels (reader GEODATABASE_FILE_2)
    attributes: OBJECTID integer, gcUnqID char(38), srcOfData char(75), srcLastEdt date, uploadAuth char(75), uploadDate date, effective date, expire date, srcUnqID char(100), parOwn char(150), parOwn2 char(150), parOwnAdd char(150), parOwnTel char(15), parAdd char(150), parNum integer, parStreet char(100), parType char(100), extResrce char(254), comments char(100), gcModDate date, gcModType char(2), gcEditBy char(100), gcException char(75), gcLabel char(150), Shape_Length double, Shape_Area double
    -> Prep_Source_Parcels
Note: Remove extra spaces
Prep_Source_Parcels: Prep Source Parcels
    COMMENTS = @Value(comments)
    EFFECTIVE = @Value(effective)
    EXPIRE = @Value(expire)
    EXTRESRCE = @Value(extResrce)
    GCEDITBY = @Value(gcEditBy)
    GCEXCEPTION = @Value(gcException)
    GCLABEL = @Value(gcLabel)
    GCMODDATE = @Value(gcModDate)
    GCMODTYPE = @Value(gcModType)
    GCUNQID = @Value(gcUnqID)
    OBJECTID = @Value(OBJECTID)
    PARADD = @Value(parAdd)
    PARNUM = @Value(parNum)
    PAROWN = @Value(parOwn)
    PAROWN2 = @Value(parOwn2)
    PAROWNADD = @Value(parOwnAdd)
    PAROWNTEL = @Value(parOwnTel)
    PARSTREET = @Value(parStreet)
    PARTYPE = @Value(parType)
    SHAPE_AREA = @Value(Shape_Area)
    SHAPE_LENGTH = @Value(Shape_Length)
    SRCLASTEDT = @Value(srcLastEdt)
    SRCOFDATA = @Value(srcOfData)
    SRCUNQID = @Value(srcUnqID)
    UPLOADAUTH = @Value(uploadAuth)
    UPLOADDATE = @Value(uploadDate)
    -> Join_Parcels [LEFT]
Join_Parcels: FeatureJoiner
    ATTR_CONFLICT_RES_LOOKUP = USE_LEFT
    GEOMETRY_HANDLING_LOOKUP = USE_LEFT
    JOIN_KEYS = psrcUnqID _ParcelID AUTO
    JOIN_MODE = Left
    ATTR_CONFLICT_RES = Prefer Left
    GEOMETRY_HANDLING = Prefer Left
    JOINED -> AttributeManager
Note: Organize and rename fields as needed
AttributeManager
    ATTR_TABLE:
      RENAME_SET_VALUE pOBJECTID > OBJECTID (int32)
      REMOVE _ParcelID (varchar(200))
      RENAME_SET_VALUE _SubdName > SubdName (varchar(200))
      RENAME_SET_VALUE psrcOfData > Source (varchar(75))
      RENAME_SET_VALUE psrcLastEdt > EditDate (datetime)
      RENAME_SET_VALUE puploadAuth > UploadAuth (varchar(75))
      RENAME_SET_VALUE puploadDate > UploadDate (datetime)
      RENAME_SET_VALUE peffective > Effective (datetime)
      RENAME_SET_VALUE pexpire > Expire (datetime)
      RENAME_SET_VALUE pparOwn > ParOwn (varchar(150))
      RENAME_SET_VALUE pparOwn2 > ParOwn2 (varchar(150))
      RENAME_SET_VALUE pparOwnAdd > ParOwn3 (varchar(150))
      RENAME_SET_VALUE pparOwnTel > ParOwnTel (varchar(15))
      RENAME_SET_VALUE pparAdd > ParAddress (varchar(150))
      RENAME_SET_VALUE pparNum > ParStNum (int32)
      RENAME_SET_VALUE pparStreet > ParStName (varchar(100))
      RENAME_SET_VALUE pparType > ParStType (varchar(100))
      RENAME_SET_VALUE pextResrce > ExtResrce (varchar(254))
      RENAME_SET_VALUE pcomments > Comments (varchar(100))
      RENAME_SET_VALUE psrcUnqID > ParcelID (varchar(100))
      REMOVE pgcModDate (datetime)
      REMOVE pgcLabel (varchar(150))
      REMOVE pgcUnqID (varchar(38))
      REMOVE pgcModType (varchar(2))
      REMOVE pgcEditBy (varchar(100))
      REMOVE pgcException (varchar(75))
      REMOVE text_line_data (buffer)
      REMOVE _ParcelInfo{} (varchar(200))
      REMOVE _element_count (uint64)
    USER_EXPOSED_ATTRIBUTES = pShape.STLength(),pShape.STArea()
    -> Filter_Out_Invalid
Note: If any parcels come through with no parcel ID, exclude them, otherwise, procceed to the writer
Filter_Out_Invalid: Tester
    BOOL_OP = COMPOSITE
    COMPOSITE_TEST = 1 OR 2 AND NOT ( 3 OR 4 OR 5 OR 6 OR 7 )
    TEST_CLAUSE:
      TEST @Value(ParcelID) CONTAINS_REGEX [0-9A-Z]{5} [0-9A-Z]{5}
      TEST @Value(ParcelID) CONTAINS_REGEX [0-9A-Z]{6} [0-9A-Z]{6}
      TEST ParcelID ATTRIBUTE_VALUE_NULL ""
      TEST ParcelID ATTRIBUTE_IS_EMPTY ""
      TEST ParcelID ATTRIBUTE_IS_MISSING ""
      TEST @Value(ParcelID) =
      TEST @Value(ParcelID) =
    TEST_MODE = TEST
    PASSED -> Change_Detector [REVISED]
Note: Bring in the existing parcels for a comparison
MapData/Parcels_Curated (reader GEODATABASE_FILE_4)
    attributes: OBJECTID integer, SubdName char(200), Source char(75), EditDate date, UploadAuth char(75), UploadDate date, Effective date, Expire date, ParOwn char(150), ParOwn2 char(150), ParOwn3 char(150), ParOwnTel char(15), ParAddress char(150), ParStNum integer, ParStName char(100), ParStType char(100), ExtResrce char(254), Comments char(100), ParcelID char(100), Shape_Length double, Shape_Area double
    -> Change_Detector [ORIGINAL]
Note: Compare against existing and ignore everything that's exactly the same. This way only new/changed features are processed. This improves performance exponentially
Change_Detector: ChangeDetector
    BLANK_AND_MISSING_DIFFER = No
    CHECK_COORDINATE_SYSTEMS = No
    CHECK_TYPES_AND_ENCODINGS = No
    LENIENT_MATCH = Yes
    MATCH = 2D
    MATCHATTRS = Comments EditDate Effective Expire ExtResrce OBJECTID ParAddress ParOwn ParOwn2 ParOwn3 ParOwnTel ParStName ParStNum ParStType ParcelID Source SubdName UploadAuth UploadDate Shape_Area Shape_Length
    MATCH_STRATEGY_LOOKUP = MATCH
    UNCHANGED_OUTPUT = Output Original
    UPSERT_MODE = No
    MATCH_STRATEGY = Match Selected Attributes
    UPDATED -> Parcels_Curated (writer GEODATABASE_FILE_3)
Parcels_Curated (writer GEODATABASE_FILE_3)
    attributes: OBJECTID integer, SubdName char(200), Source char(75), EditDate date, UploadAuth char(75), UploadDate date, Effective date, Expire date, ParOwn char(150), ParOwn2 char(150), ParOwn3 char(150), ParOwnTel char(15), ParAddress char(150), ParStNum integer, ParStName char(100), ParStType char(100), ExtResrce char(254), Comments char(100), ParcelID char(100), pShape_Length double, pShape_Area double

FME custom transformer Subd Name Cleaners
Extracts info from the parcels info text files sent by the Assessor's Office

Parameters:
- TEXT_LINE_DATA = @Value(text_line_data)   # Text Line Data
- _SUBDNAME = @Value(_SubdName)   # Subdname
- FME_PROCESS_GROUP_BY =   # "" Group By
- FME_PROCESS_GROUPS_ORDERED = No   # When All Features Received,No%When Group Changes (Advanced),Yes Complete Groups

Input (input)
    -> Clean_Init_Space
Note: Remove double, leading, and trailing spaces. Loop back to this if spaces are found at the end again
Note: Loop to here to run through scenarios again if needed
Note: Dashes need special logic because there are legitimate uses in names
Note: regex
Note: Clean up some strings for easier handling as well
Note: regex
Note: Deal with scenarios that Regex can't handle because of special characters that are part of the RegEx syntax. Use simple text matching and replacements instead
Note: Replace text using regex based on specific senarios
Note: regex
start_of_scenarios (input)
    -> filter_legitimate_uses
Note: Note: This tool uses all UPPER CASE characters. Change to upper case if needed.
Note: If initials appear to be legitimate (like in MLK Junior), and one or more of the initials was seen as a roman numeral & changed to a number, change it back to the respective letter.
Note: Look for double spaces again. If found, sent to start, so the logic can be checked again
Note: regex
Note: Check all scenarios again to account for instances where more than one scenario was found in a string and the replacements changed the string formatting in the first pass (extra spaces, etc.)
check_all_scenarios_again: Tester
    BOOL_OP = OR
    TEST_CLAUSE:
      CASE_INSENSITIVE_TEST @Value(_SubdName) CONTAINS_REGEX \b((RE\s*(S|V|SUB|VISION|SUBDV|SUBDIVISION)?(S|V)?|ADD(N|ITION)?(S)?|P(ART|T)?(S)?|SD|AMEND(MENT)?(S)?)\s+(OF|TO)).*|\b(?:\d{1,3}(?:ST|ND|RD|TH)\s*)?(?:PT|PART|RE(S)?(UB)?(DIVISION)?|REV(ISION)?|REFLECTIONS|SUB(D)?(V)?(ISION)?|SD|RE\s*SUB|PLAT|AMEND(MENT)?|ADD(N)|ADDITION|PLA(N)?|REV\s*PLAN)\s*(?:OF|TO)\s*(?:THE|TO)?|(OF\s*TO\s*(\d+)?)\b|\d{1,3}(?:ST|ND|RD|TH)$
      CASE_SENSITIVE_TEST @Value(_SubdName) CONTAINS_REGEX \bZZZ\s*([A-Z]{1}|\d+)\b|\b(?:\d+[A-Z]+|[A-Z]+\d+|\d+|[A-Z]{1})(\s*-\s*)(?:\d+[A-Z]+|[A-Z]+\d+|\d+|[A-Z]{1})\b|\b(?:\d+(ST|ND|RD|TH)\s*)?ZZZ(?:\s*\d+(ST|ND|RD|TH))?|\b(\d{1}[A-Z]{1}|[A-Z]{1}\d{1})\b
      CASE_SENSITIVE_TEST @Value(_SubdName) CONTAINS_REGEX ^(TO|AND|ABOUT|LIKE|ABOVE|NEAR|ACROSS|OF|AFTER|OFF|AGAINST|ON|ALONG|ONTO|AMONG|OPPOSITE|AROUND|OUT|AS|OUTSIDE|AT|OVER|BEFORE|PAST|BEHIND|ROUND|BELOW|SINCE|BENEATH|THAN|BESIDE|THROUGH|BETWEEN|TO|BEYOND|TOWARDS|BY|UNDER|DESPITE|UNDERNEATH|DOWN|UNLIKE|DURING|UNTIL|EXCEPT|UP|FOR|UPON|FROM|VIA|IN|WITH|INSIDE|WITHIN|INTO|WITHOUT)\b|\b(TO|AND|ABOUT|LIKE|ABOVE|NEAR|ACROSS|OF|AFTER|OFF|AGAINST|ON|ALONG|ONTO|AMONG|OPPOSITE|AROUND|OUT|AS|OUTSIDE|AT|OVER|BEFORE|PAST|BEHIND|ROUND|BELOW|SINCE|BENEATH|THAN|BESIDE|THROUGH|BETWEEN|TO|BEYOND|TOWARDS|BY|UNDER|DESPITE|UNDERNEATH|DOWN|UNLIKE|DURING|UNTIL|EXCEPT|UP|FOR|UPON|FROM|VIA|IN|WITH|INSIDE|WITHIN|INTO|WITHOUT|THE)$
      CASE_SENSITIVE_TEST @Value(_SubdName) CONTAINS_REGEX (?<=^|\b)(ADD(N)?|BL(O)?K|PH(\d+)?|RE(V)?|SEC|LOT|PAR|TWP|TRCT|AREA|PART|PT|(RE)?SUB(D|V)?(IVISION)?|SUBDV|SUB|RE\s*SUB|AMEN(D)?(ED)?(\s*PLAN)?|AMEN(D)?(MENT)?|(RE|UN)?REC(ORDED)?|UNRE(ORDD)?|FINAL\s*PLA(N|T)?|OUTLINE\s*PLA(N|T)?|PROPOSED|P\s*D|SD|RES(TATED)?|(RE)?PLA(N|T|TTING)?(S)?|C\s*U\s*(P)?|P\s*U\s*(D|C)?|C\s*P|R\s*R|B\s*L|\s*&)(?=\b|$)
      CASE_SENSITIVE_TEST @Value(_SubdName) CONTAINS_REGEX (?<=\d\s|^)\d+|\d+(?=\s\d|$)
    TEST_MODE = CASE_INSENSITIVE_TEST
    PASSED -> start_of_scenarios (output)
    FAILED -> Output (output)
Output (output)
Note: regex
start_of_scenarios (output)

Bookmark: Preemptively Remove Extra Spaces
Init_Space (input)
    -> Clean_Init_Space
Clean_Init_Space: StringReplacer
    CASE = NO
    FIND_TEXT = "  "
    NO_MATCH = _FME_NO_OP_
    REGEXP = NO
    REPLACE_TEXT = " "
    SRC_ATTRS = _SubdName
    -> filter_legitimate_uses

Bookmark: Dash Scenarios
filter_legitimate_uses: Tester
    BOOL_OP = COMPOSITE
    COMPOSITE_TEST = 1 OR 2 OR 3 AND 4
    TEST_CLAUSE:
      CASE_INSENSITIVE_TEST @Value(_SubdName) BEGINS_WITH -
      CASE_INSENSITIVE_TEST @Value(_SubdName) ENDS_WITH -
      CASE_INSENSITIVE_TEST @Value(_SubdName) CONTAINS_REGEX (?:^|\b\s)(\w{1,2}-\w{1,2}|\w{1,2}-|-\w{1,2})(?:$|\b|\s)
      CASE_INSENSITIVE_TEST @Value(_SubdName) NOT_CONTAINS_REGEX \b[A-Z]+-[A-Z]+\b|\b[A-Z]+\s-\s[A-Z]+\b
    TEST_MODE = CASE_INSENSITIVE_TEST
    PASSED -> dash_begin_or_end
    FAILED -> Junction
dash_begin_or_end: StringReplacer
    CASE = NO
    FIND_TEXT = -
    NO_MATCH = _FME_NO_OP_
    REGEXP = NO
    REPLACE_TEXT = " "
    SRC_ATTRS = _SubdName
    -> Junction
Junction
    -> double_amps

Bookmark: Preemptive cleanup of strings
double_amps: StringReplacer
    CASE = NO
    FIND_TEXT = & &
    NO_MATCH = _FME_NO_OP_
    REGEXP = YES
    REPLACE_TEXT = &
    SRC_ATTRS = _SubdName
    -> and_to_amp
and_to_amp: StringReplacer
    CASE = NO
    FIND_TEXT = \bAND\b
    NO_MATCH = _FME_NO_OP_
    REGEXP = YES
    REPLACE_TEXT = &
    SRC_ATTRS = _SubdName
    -> SD_OF

Bookmark: Non regex scenarios
SD_OF: StringReplacer
    CASE = NO
    FIND_TEXT = S/D OF
    NO_MATCH = _FME_NO_OP_
    REGEXP = NO
    REPLACE_TEXT = SD OF
    SRC_ATTRS = _SubdName
    -> SD_2
SD_2: StringReplacer
    CASE = NO
    FIND_TEXT = S/D
    NO_MATCH = _FME_NO_OP_
    REGEXP = NO
    REPLACE_TEXT = SD
    SRC_ATTRS = _SubdName
    -> PO
PO: StringReplacer
    CASE = NO
    FIND_TEXT = P/O
    NO_MATCH = _FME_NO_OP_
    REGEXP = NO
    REPLACE_TEXT = PO
    SRC_ATTRS = _SubdName
    -> RE-SD
RE-SD: StringReplacer
    CASE = NO
    FIND_TEXT = RE-S/D
    NO_MATCH = _FME_NO_OP_
    REGEXP = NO
    REPLACE_TEXT = RESUB
    SRC_ATTRS = _SubdName
    -> PT
PT: StringReplacer
    CASE = NO
    FIND_TEXT = P/T
    NO_MATCH = _FME_NO_OP_
    REGEXP = NO
    REPLACE_TEXT = PT
    SRC_ATTRS = _SubdName
    -> OUTLINE_FINAL
Note: Unique handling. This one can be safely removed because it's not used in any logic after this point
OUTLINE_FINAL: StringReplacer
    CASE = NO
    FIND_TEXT = OUTLINE/FINAL
    NO_MATCH = _FME_NO_OP_
    REGEXP = NO
    REPLACE_TEXT = " "
    SRC_ATTRS = _SubdName
    -> re_1st_pass

Bookmark: Primary regex scenarios
Note: Descriptive phrases
Note: Examples: / "RESUBDIVISION OF" in RESUBDIVISION OF LOT 10" / "PART OF" in "PART OF BLOCK A" / "2ND AMENDMENT TO" in "2ND AMENDMENT TO THE PLAT" / "SUBDIVISION TO" in "SUBDIVISION TO LOT 5" / "35TH REVISED PLAN OF" in "35TH REVISED PLAN OF THE ESTATES"
re_1st_pass: StringReplacer
    CASE = NO
    FIND_TEXT = \b((RE\s*(S|V|SUB|VISION|SUBDV|SUBDIVISION)?(S|V)?|ADD(N|ITION)?(S)?|P(ART|T)?(S)?|SD|AMEND(MENT)?(S)?)\s+(OF|TO)).*|\b(?:\d{1,3}(?:ST|ND|RD|TH)\s*)?(?:PT|PART|RE(S)?(UB)?(DIVISION)?|REV(ISION)?|REFLECTIONS|SUB(D)?(V)?(ISION)?|SD|RE\s*SUB|PLAT|AMEND(MENT)?|ADD(N)|ADDITION|PLA(N)?|REV\s*PLAN)\s*(?:OF|TO)\s*(?:THE|TO)?|(OF\s*TO\s*(\d+)?)\b|\d{1,3}(?:ST|ND|RD|TH)$
    NO_MATCH = _FME_NO_OP_
    REGEXP = YES
    REPLACE_TEXT = " "
    SRC_ATTRS = _SubdName
    TEST_STRING:
      WILSON RE OF JAMERSON & WRIGHT ADDN
      BOALS REV OF LOT 17 BARTON & LAMB BLK 1
      MURLEY REV OF LOT 46 49 TO 54
      WOODS LANDING OF THE VILL OF BENNGTON PH
      AREA A CHURCH OF THE HOLY APOSTLES PD
      THEAT RE SUB OF TRANS OF THE TEST
      GARRETTS REV PLAN OF GOODMAN BROS
      CHIMNEYHILL CONDOS AMEND TO THE RESTATED
    -> re_2nd_pass
Note: Keyword alphanumeric combinations
Note: Examples: / "ZZZ 5" in "ZZZ 5 is the code" / "A - 10" in "Section A - 10 is complete" / "25TH ZZZ" in "25TH ZZZ Avenue" / "B7" in "Building B7 is under construction" / "3C" in "Room 3C is occupied"
re_2nd_pass: StringReplacer
    CASE = NO
    FIND_TEXT = \bZZZ\s*([A-Z]{1}|\d+)\b|\b(?:\d+[A-Z]+|[A-Z]+\d+|\d+|[A-Z]{1})(\s*-\s*)(?:\d+[A-Z]+|[A-Z]+\d+|\d+|[A-Z]{1})\b|\b(?:\d+(ST|ND|RD|TH)\s*)?ZZZ(?:\s*\d+(ST|ND|RD|TH))?|\b(\d{1}[A-Z]{1}|[A-Z]{1}\d{1})\b
    NO_MATCH = _FME_NO_OP_
    REGEXP = YES
    REPLACE_TEXT = " "
    SRC_ATTRS = _SubdName
    -> re_3rd_pass
Note: Articles at the beginning or end
Note: Pending: Needs specific verification to make sure we're not deleting parts of names
Note: Examples: / "TO" in "TO the market" / "ABOUT" in "ABOUT the situation" / "UNDER" in "UNDER the bridge" / "WITHOUT" in "WITHOUT hesitation" / "BETWEEN" in "BETWEEN the lines"
re_3rd_pass: StringReplacer
    CASE = NO
    FIND_TEXT = ^(TO|AND|ABOUT|LIKE|ABOVE|NEAR|ACROSS|OF|AFTER|OFF|AGAINST|ON|ALONG|ONTO|AMONG|OPPOSITE|AROUND|OUT|AS|OUTSIDE|AT|OVER|BEFORE|PAST|BEHIND|ROUND|BELOW|SINCE|BENEATH|THAN|BESIDE|THROUGH|BETWEEN|TO|BEYOND|TOWARDS|BY|UNDER|DESPITE|UNDERNEATH|DOWN|UNLIKE|DURING|UNTIL|EXCEPT|UP|FOR|UPON|FROM|VIA|IN|WITH|INSIDE|WITHIN|INTO|WITHOUT)\b|\b(TO|AND|ABOUT|LIKE|ABOVE|NEAR|ACROSS|OF|AFTER|OFF|AGAINST|ON|ALONG|ONTO|AMONG|OPPOSITE|AROUND|OUT|AS|OUTSIDE|AT|OVER|BEFORE|PAST|BEHIND|ROUND|BELOW|SINCE|BENEATH|THAN|BESIDE|THROUGH|BETWEEN|TO|BEYOND|TOWARDS|BY|UNDER|DESPITE|UNDERNEATH|DOWN|UNLIKE|DURING|UNTIL|EXCEPT|UP|FOR|UPON|FROM|VIA|IN|WITH|INSIDE|WITHIN|INTO|WITHOUT|THE)$
    NO_MATCH = _FME_NO_OP_
    REGEXP = YES
    REPLACE_TEXT = " "
    SRC_ATTRS = _SubdName
    -> re_4th_pass
Note: Standalone keyphrases
Note: Examples: / "ADD" in "ADD the new section" / "BLOCK" in "BLOCK A is ready" / "PH2" in "PH2 of the plan" / "LOT" in "LOT 5 is available" / "PUD" in "PUD zoning is approved"
re_4th_pass: StringReplacer
    CASE = NO
    FIND_TEXT = (?<=^|\b)(ADD(N)?|BL(O)?K|PH(\d+)?|RE(V)?|SEC|LOT|PAR|TWP|TRCT|AREA|PART|PT|(RE)?SUB(D|V)?(IVISION)?|SUBDV|SUB|RE\s*SUB|AMEN(D)?(ED)?(\s*PLAN)?|AMEN(D)?(MENT)?|(RE|UN)?REC(ORDED)?|UNRE(ORDD)?|FINAL\s*PLA(N|T)?|OUTLINE\s*PLA(N|T)?|PROPOSED|P\s*D|SD|RES(TATED)?|(RE)?PLA(N|T|TTING)?(S)?|C\s*U\s*(P)?|P\s*U\s*(D|C)?|C\s*P|R\s*R|B\s*L|\s*&)(?=\b|$)
    NO_MATCH = _FME_NO_OP_
    REGEXP = YES
    REPLACE_TEXT = " "
    SRC_ATTRS = _SubdName
    -> re_5th_pass
Note: Standalone numbers
Note: Examples: / "5" in "5 rooms available" / "10" in "The meeting is at 10 AM" / "25" in "25 new projects launched" / "100" in "100 items were sold" / "50" in "50 people attended the event"
re_5th_pass: StringReplacer
    CASE = NO
    FIND_TEXT = (?<=\d\s|^)\d+|\d+(?=\s\d|$)
    NO_MATCH = _FME_NO_OP_
    REGEXP = YES
    REPLACE_TEXT = " "
    SRC_ATTRS = _SubdName
    -> if_legitimate_initials

Bookmark: Deal with initials
if_legitimate_initials: Tester
    BOOL_OP = OR
    TEST_CLAUSE = CASE_SENSITIVE_TEST @Value(_SubdName) CONTAINS_REGEX \b([A-Z]{1}|1|5|10)\s(1|5|10)\b|\b(1|5|10)\s([A-Z]{1}|1|5|10)\b
    TEST_MODE = CASE_SENSITIVE_TEST
    PASSED -> filter_by_specific_init
    FAILED -> Junction_2
filter_by_specific_init: TestFilter
    DEFAULT_VALUE = <UNFILTERED>
    PASSED_TEST_GROUP_OUTPUT = FIRST
    TEST_LIST = "BOOL_OP,OR,COMPOSITE_TEST,""""""1"""""",TEST_CLAUSE,CASE_SENSITIVE_TEST @Value(_SubdName) CONTAINS_REGEX \b1\b",I - 1,"BOOL_OP,OR,COMPOSITE_TEST,""""""1"""""",TEST_CLAUSE,CASE_SENSITIVE_TEST @Value(_SubdName) CONTAINS_REGEX \b5\b",V - 5,"BOOL_OP,OR,COMPOSITE_TEST,""""""1"""""",TEST_CLAUSE,CASE_SENSITIVE_TEST @Value(_SubdName) CONTAINS_REGEX \b10\b",X - 10
    I - 1 -> from_1_to_I
    V - 5 -> from_5_to_V
    X - 10 -> from_10_to_X
    <UNFILTERED> -> Junction_2
from_1_to_I: StringReplacer
    CASE = NO
    FIND_TEXT = \b1\b
    NO_MATCH = _FME_NO_OP_
    REGEXP = YES
    REPLACE_TEXT = I
    SRC_ATTRS = _SubdName
    -> Junction_2
from_5_to_V: StringReplacer
    CASE = NO
    FIND_TEXT = \b5\b
    NO_MATCH = _FME_NO_OP_
    REGEXP = YES
    REPLACE_TEXT = V
    SRC_ATTRS = _SubdName
    -> Junction_2
from_10_to_X: StringReplacer
    CASE = NO
    FIND_TEXT = \b10\b
    NO_MATCH = _FME_NO_OP_
    REGEXP = YES
    REPLACE_TEXT = X
    SRC_ATTRS = _SubdName
    -> Junction_2
Junction_2
    -> Tim_at_ends

Bookmark: Check for spaces again
Tim_at_ends: AttributeTrimmer
    SRC_ATTRS = _SubdName
    TRIM_CHARS = " "
    TRIM_TO_NONE = Yes
    TRIM_TYPE = BOTH
    -> Check_for_spaces_again
Check_for_spaces_again: Tester
    BOOL_OP = OR
    TEST_CLAUSE = CASE_INSENSITIVE_TEST @Value(_SubdName) CONTAINS
    TEST_MODE = CASE_INSENSITIVE_TEST
    PASSED -> Init_Space (output)
    FAILED -> check_all_scenarios_again
Init_Space (output)

FME custom transformer Prep Source Parcels

Parameters:
- COMMENTS = @Value(comments)   # comments
- EFFECTIVE = @Value(effective)   # effective
- EXPIRE = @Value(expire)   # expire
- EXTRESRCE = @Value(extResrce)   # extResrce
- GCEDITBY = @Value(gcEditBy)   # gcEditBy
- GCEXCEPTION = @Value(gcException)   # gcException
- GCLABEL = @Value(gcLabel)   # gcLabel
- GCMODDATE = @Value(gcModDate)   # gcModDate
- GCMODTYPE = @Value(gcModType)   # gcModType
- GCUNQID = @Value(gcUnqID)   # gcUnqID
- OBJECTID = @Value(OBJECTID)
- PARADD = @Value(parAdd)   # parAdd
- PARNUM = @Value(parNum)   # parNum
- PAROWN = @Value(parOwn)   # parOwn
- PAROWN2 = @Value(parOwn2)   # parOwn2
- PAROWNADD = @Value(parOwnAdd)   # parOwnAdd
- PAROWNTEL = @Value(parOwnTel)   # parOwnTel
- PARSTREET = @Value(parStreet)   # parStreet
- PARTYPE = @Value(parType)   # parType
- SRCLASTEDT = @Value(srcLastEdt)   # srcLastEdt
- SRCOFDATA = @Value(srcOfData)   # srcOfData
- SRCUNQID = @Value(srcUnqID)   # srcUnqID
- UPLOADAUTH = @Value(uploadAuth)   # uploadAuth
- UPLOADDATE = @Value(uploadDate)   # uploadDate
- SHAPE_AREA = @Value(Shape_Area)   # Shape Area
- SHAPE_LENGTH = @Value(Shape_Length)   # Shape Length

Note: Reproject to state plane if needed
Reproject_Parcels: EsriReprojector [off]
    DEST = ESRIWKT|NAD_1983_StatePlane_Tennessee_FIPS_4100_Feet|PROJCS["NAD_1983_StatePlane_Tennessee_FIPS_4100_Feet",GEOGCS["GCS_North_American_1983",DATUM["D_North_American_1983",SPHEROID["GRS_1980",6378137.0,298.257222101]],PRIMEM["Greenwich",0.0],UNIT["Degree",0.0174532925199433]],PROJECTION["Lambert_Conformal_Conic"],PARAMETER["False_Easting",1968500.0],PARAMETER["False_Northing",0.0],PARAMETER["Central_Meridian",-86.0],PARAMETER["Standard_Parallel_1",35.25],PARAMETER["Standard_Parallel_2",36.41666666666666],PARAMETER["Latitude_Of_Origin",34.33333333333334],UNIT["Foot_US",0.3048006096012192]]
    GEOTRANSFORMATION_NAME = WGS_1984_(ITRF00)_To_NAD_1983
    INTERPOLATION_TYPE = ,NearestNeighbor
    RASTER_CELL_SIZE_LOOKUP = ,PreserveCells
    RASTER_TOLERANCE = 0.0
    SOURCE = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    INTERPOLATION_TYPE_NAME = Nearest Neighbor
    RASTER_CELL_SIZE = Preserve Cells
Input (input)
    -> Rename_Parcels
Note: Rename incoming fields to make it clear where they are coming from
Rename_Parcels: BulkAttributeRenamer
    ATTRCHOICE_ACTION = NONPROTECTEDFME
    MODE_CHOICE = RENAME
    PATTERN_ACTION_DISP = ADDPREFIX
    REPLACE_STR = p
    ATTRCHOICE = All Attributes
    -> Replace_Double_Spaces
Spaces_Loop (input)
    -> Replace_Double_Spaces
Note: Reduce double spaces to single spaces
Replace_Double_Spaces: StringReplacer
    CASE = NO
    FIND_TEXT = "  "
    NO_MATCH = _FME_NO_OP_
    REGEXP = YES
    REPLACE_TEXT = " "
    SRC_ATTRS = psrcUnqID
    -> Check_Spaces_Again
Note: Check to see if any other spaces were found. / Send back if found. Else continue...
Check_Spaces_Again: Tester
    BOOL_OP = OR
    TEST_CLAUSE = CASE_SENSITIVE_TEST @Value(psrcUnqID) CONTAINS_REGEX
    TEST_MODE = TEST
    PASSED -> Spaces_Loop (output)
    FAILED -> Timmer_Ends
Note: Do a trim on the ends
Timmer_Ends: AttributeTrimmer
    SRC_ATTRS = psrcUnqID
    TRIM_CHARS = " "
    TRIM_TO_NONE = Yes
    TRIM_TYPE_TCL = trim
    TRIM_TYPE = Both
    -> Output (output)
Output (output)
Spaces_Loop (output)

FME custom transformer Subd Name Replacement

Parameters:
- TEXT_LINE_DATA = @Value(text_line_data)   # Text Line Data
- FME_PROCESS_GROUP_BY =   # "" Group By
- FME_PROCESS_GROUPS_ORDERED = No   # When All Features Received,No%When Group Changes (Advanced),Yes Complete Groups

Note: First split attributes by comma, then map to a permanent field (take it out of a list), and then remove the "" from said field
Note: The following characters can't be matched literally in regex queries because they are part of the syntax and can't be matched individually through regex. These need to be replaced using regular text queries: .\/[]() / The following characters are also part of the syntax but they *can* be matched individually. These are OK to replace here through regex: {},:;
Note: NOTE: An exemption is dashes. Many of those are legitimate and can't be wholesale replaced here without some special logic. That logic is handled later
Input (input)
    -> Split_by_QCommaQ
Note: Change spelled out ordinals to the / numeric versions for easier handling later
Note: Examples: / 3RD -----> 3RD / FOURTH -----> 4TH
Note: Then remove spelled out numbers if they're accompanied by known descriptors like "Phase," "Block," etc. ZZZ is used as a string to be removed later
Note: Examples: / PHASE ONE ----> ZZZ / FOUR SEC ----> ZZZ
Note: Do the same for the descriptors by themselves
Note: Replace roman numerals with their numeric equivalents
Note: Example: the "II" in Phase II A"
Junction_32
    -> Output (output)
Output (output)

Bookmark: Prep fields
Split_by_QCommaQ: AttributeSplitter
    ATTR_NAME = text_line_data
    DELIMITER = ,
    DROP_EMPTY_PARTS = NO
    LIST_NAME = _ParcelInfo
    TRIM_TYPE = BOTH
    -> County_Total_Elements
County_Total_Elements: ListElementCounter
    CNT_ATTR = _element_count
    LIST_NAME = _ParcelInfo{}
    -> Filter_Out_Erratic
Note: If the number of elements is standard (12), continue. Else, send through the uncommon counts section below
Filter_Out_Erratic: Tester
    BOOL_OP = OR
    TEST_CLAUSE = NUM_TEST @Value(_element_count) = 12
    TEST_MODE = NUM_TEST
    PASSED -> element_12
    FAILED -> Uncommon_counts
element_12: AttributeCreator
    ATTR_TABLE:
      SET_TO _SubdName (varchar(200)) = @Value(_ParcelInfo{10})
      SET_TO _ParcelID (varchar(200)) = @Value(_ParcelInfo{0})
    -> Junction_2
Uncommon_counts: TestFilter
    DEFAULT_VALUE = <UNFILTERED>
    PASSED_TEST_GROUP_OUTPUT = FIRST
    TEST_LIST = "BOOL_OP,OR,COMPOSITE_TEST,""""""1"""""",TEST_CLAUSE,TEST @Value(_element_count) = 13",13,"BOOL_OP,OR,COMPOSITE_TEST,""""""1"""""",TEST_CLAUSE,TEST @Value(_element_count) = 14",14,"BOOL_OP,OR,COMPOSITE_TEST,""""""1"""""",TEST_CLAUSE,TEST @Value(_element_count) = 15",15,"BOOL_OP,OR,COMPOSITE_TEST,""""""1"""""",TEST_CLAUSE,TEST @Value(_element_count) = 16",16,"BOOL_OP,OR,COMPOSITE_TEST,""""""1"""""",TEST_CLAUSE,TEST @Value(_element_count) = 17",17,"BOOL_OP,OR,COMPOSITE_TEST,""""""1"""""",TEST_CLAUSE,TEST @Value(_element_count) = 18",18,"BOOL_OP,OR,COMPOSITE_TEST,""""""1"""""",TEST_CLAUSE,TEST @Value(_element_count) = 19",19,"BOOL_OP,OR,COMPOSITE_TEST,""""""1"""""",TEST_CLAUSE,TEST @Value(_element_count) = 20",20,"BOOL_OP,OR,COMPOSITE_TEST,""""""1"""""",TEST_CLAUSE,TEST @Value(_element_count) = 21",21
    13 -> element_13
    14 -> element_14
    15 -> element_15
    16 -> element_16
    17 -> element_17
    18 -> element_18
    19 -> element_19
    20 -> element_20
    21 -> element_21
    <UNFILTERED> -> Terminator
element_13: AttributeCreator
    ATTR_TABLE:
      SET_TO _SubdName (varchar(200)) = @Value(_ParcelInfo{11})
      SET_TO _ParcelID (varchar(200)) = @Value(_ParcelInfo{0})
    -> Junction
element_18: AttributeCreator
    ATTR_TABLE:
      SET_TO _SubdName (varchar(200)) = @Value(_ParcelInfo{16})
      SET_TO _ParcelID (varchar(200)) = @Value(_ParcelInfo{0})
    -> Junction
element_14: AttributeCreator
    ATTR_TABLE:
      SET_TO _SubdName (varchar(200)) = @Value(_ParcelInfo{12})
      SET_TO _ParcelID (varchar(200)) = @Value(_ParcelInfo{0})
    -> Junction
element_19: AttributeCreator
    ATTR_TABLE:
      SET_TO _SubdName (varchar(200)) = @Value(_ParcelInfo{17})
      SET_TO _ParcelID (varchar(200)) = @Value(_ParcelInfo{0})
    -> Junction
element_15: AttributeCreator
    ATTR_TABLE:
      SET_TO _SubdName (varchar(200)) = @Value(_ParcelInfo{13})
      SET_TO _ParcelID (varchar(200)) = @Value(_ParcelInfo{0})
    -> Junction
element_20: AttributeCreator
    ATTR_TABLE:
      SET_TO _SubdName (varchar(200)) = @Value(_ParcelInfo{18})
      SET_TO _ParcelID (varchar(200)) = @Value(_ParcelInfo{0})
    -> Junction
element_16: AttributeCreator
    ATTR_TABLE:
      SET_TO _SubdName (varchar(200)) = @Value(_ParcelInfo{14})
      SET_TO _ParcelID (varchar(200)) = @Value(_ParcelInfo{0})
    -> Junction
element_21: AttributeCreator
    ATTR_TABLE:
      SET_TO _SubdName (varchar(200)) = @Value(_ParcelInfo{21})
      SET_TO _ParcelID (varchar(200)) = @Value(_ParcelInfo{0})
    -> Junction
Note: This initial parsing is critical. Make sure that all scenarios are accounted for. Stop the tool with an error message otherwise
Terminator
    MESSAGE = Translation Terminated: unaccounted for element count found in Subd Name Replacement test filter
element_17: AttributeCreator
    ATTR_TABLE:
      SET_TO _SubdName (varchar(200)) = @Value(_ParcelInfo{15})
      SET_TO _ParcelID (varchar(200)) = @Value(_ParcelInfo{0})
    -> Junction
Junction
    -> Junction_2

Bookmark: Remove Spec Characters
Junction_2
    -> Remove_Apostrophes
Spec_Character_Loop (input)
    -> Remove_Apostrophes
Note: Special logic needed for ' because there are legitimate cases of their use
Remove_Apostrophes: StringReplacer
    CASE = NO
    FIND_TEXT = (["'])([A-Z\d]+-?[A-Z\d]+)\1
    NO_MATCH = _FME_NO_OP_
    REGEXP = YES
    REPLACE_TEXT = " "
    SRC_ATTRS = _SubdName
    -> Remove_Spec_Characters
Remove_Spec_Characters: StringReplacer
    CASE = NO
    FIND_TEXT = ("|#|`|;|@|:|~|%)
    NO_MATCH = _FME_NO_OP_
    REGEXP = YES
    REPLACE_TEXT = " "
    SRC_ATTRS = _SubdName,_ParcelID
    TEST_STRING = Enter a string to test here...
    -> Replace_Parenthesis
Replace_Parenthesis: StringReplacer
    CASE = NO
    FIND_TEXT = (
    NO_MATCH = _FME_NO_OP_
    REGEXP = NO
    REPLACE_TEXT = " "
    SRC_ATTRS = _SubdName
    -> Replace_Parenthesis_2
Replace_Parenthesis_2: StringReplacer
    CASE = NO
    FIND_TEXT = )
    NO_MATCH = _FME_NO_OP_
    REGEXP = NO
    REPLACE_TEXT = " "
    SRC_ATTRS = _SubdName
    -> Replace_Periods
Replace_Periods: StringReplacer
    CASE = NO
    FIND_TEXT = .
    NO_MATCH = _FME_NO_OP_
    REGEXP = NO
    REPLACE_TEXT = " "
    SRC_ATTRS = _SubdName
    -> back_slash
back_slash: StringReplacer
    CASE = NO
    FIND_TEXT = \
    NO_MATCH = _FME_NO_OP_
    REGEXP = NO
    REPLACE_TEXT = " "
    SRC_ATTRS = _SubdName
    -> fwd_slash
fwd_slash: StringReplacer
    CASE = NO
    FIND_TEXT = /
    NO_MATCH = _FME_NO_OP_
    REGEXP = NO
    REPLACE_TEXT = " "
    SRC_ATTRS = _SubdName
    -> Re-check
Re-check: Tester
    BOOL_OP = OR
    TEST_CLAUSE:
      CASE_INSENSITIVE_TEST @Value(_SubdName) CONTAINS_REGEX ("|#|`|;|@|:|~)
      CASE_INSENSITIVE_TEST @Value(_SubdName) CONTAINS_REGEX (["'])([A-Z\d]+-?[A-Z\d]+)\1
      CASE_INSENSITIVE_TEST @Value(_SubdName) CONTAINS (
      CASE_INSENSITIVE_TEST @Value(_SubdName) CONTAINS )
      CASE_INSENSITIVE_TEST @Value(_SubdName) CONTAINS .
      CASE_INSENSITIVE_TEST @Value(_SubdName) CONTAINS \
    TEST_MODE = CASE_INSENSITIVE_TEST
    PASSED -> Spec_Character_Loop (output)
    FAILED -> if_legitimate_amp
Spec_Character_Loop (output)

Bookmark: Amps handling - part 1
Note: Find legitimate uses of &
if_legitimate_amp: Tester
    BOOL_OP = OR
    TEST_CLAUSE = CASE_INSENSITIVE_TEST @Value(_SubdName) CONTAINS_REGEX \b([A-Z]|\d){1}\s*&\s*([A-Z]|\d){1}\b
    TEST_MODE = CASE_INSENSITIVE_TEST
    PASSED -> FIRST_TO_1ST
    FAILED -> re_amp_erase
Note: If legitimate, continue..
Note: Otherwise remove it
re_amp_erase: StringReplacer
    CASE = NO
    FIND_TEXT = &
    NO_MATCH = _FME_NO_OP_
    REGEXP = YES
    REPLACE_TEXT = " "
    SRC_ATTRS = _SubdName
    -> FIRST_TO_1ST

Bookmark: Replace Spelled Out Numbers with Numbers (FIRST to 1ST)
FIRST_TO_1ST: StringReplacer
    CASE = NO
    FIND_TEXT = \bFIRST\b
    NO_MATCH = _FME_NO_OP_
    REGEXP = YES
    REPLACE_TEXT = 1ST
    SRC_ATTRS = _SubdName
    -> SECOND_TO_2ND
SECOND_TO_2ND: StringReplacer
    CASE = NO
    FIND_TEXT = \bSECOND\b
    NO_MATCH = _FME_NO_OP_
    REGEXP = YES
    REPLACE_TEXT = 2ND
    SRC_ATTRS = _SubdName
    -> THIRD_TO_3RD
THIRD_TO_3RD: StringReplacer
    CASE = NO
    FIND_TEXT = \bTHIRD\b
    NO_MATCH = _FME_NO_OP_
    REGEXP = YES
    REPLACE_TEXT = 3RD
    SRC_ATTRS = _SubdName
    -> FOURTH_TO_4TH
FOURTH_TO_4TH: StringReplacer
    CASE = NO
    FIND_TEXT = \bFOURTH\b
    NO_MATCH = _FME_NO_OP_
    REGEXP = YES
    REPLACE_TEXT = 4TH
    SRC_ATTRS = _SubdName
    -> FIFTH_TO_5TH
FIFTH_TO_5TH: StringReplacer
    CASE = NO
    FIND_TEXT = \bFIFTH\b
    NO_MATCH = _FME_NO_OP_
    REGEXP = YES
    REPLACE_TEXT = 5TH
    SRC_ATTRS = _SubdName
    -> SIXTH_TO_6TH
SIXTH_TO_6TH: StringReplacer
    CASE = NO
    FIND_TEXT = \bSIXTH\b
    NO_MATCH = _FME_NO_OP_
    REGEXP = YES
    REPLACE_TEXT = 6TH
    SRC_ATTRS = _SubdName
    -> SEVENTH_TO_7TH
SEVENTH_TO_7TH: StringReplacer
    CASE = NO
    FIND_TEXT = \bSEVENTH\b
    NO_MATCH = _FME_NO_OP_
    REGEXP = YES
    REPLACE_TEXT = 7TH
    SRC_ATTRS = _SubdName
    -> EIGHTH_TO_8TH
EIGHTH_TO_8TH: StringReplacer
    CASE = NO
    FIND_TEXT = \bEIGHTH\b
    NO_MATCH = _FME_NO_OP_
    REGEXP = YES
    REPLACE_TEXT = 8TH
    SRC_ATTRS = _SubdName
    -> NINTH_TO_9TH
NINTH_TO_9TH: StringReplacer
    CASE = NO
    FIND_TEXT = \bNINTH\b
    NO_MATCH = _FME_NO_OP_
    REGEXP = YES
    REPLACE_TEXT = 9TH
    SRC_ATTRS = _SubdName
    -> TENTH_TO_10TH
TENTH_TO_10TH: StringReplacer
    CASE = NO
    FIND_TEXT = \bTENTH\b
    NO_MATCH = _FME_NO_OP_
    REGEXP = YES
    REPLACE_TEXT = 10TH
    SRC_ATTRS = _SubdName
    -> remove_numbers

Bookmark: Replace numbers
remove_numbers: StringReplacer
    CASE = NO
    FIND_TEXT = \b(?:LT|LOT|BL(?:CK|K|OCK)|PH(?:ASE)?|AD(?:D|DITION|DN|DT)?|PA(?:R|RCEL)?|SEC(?:T|TION)?|TR(?:A|C|T)?|REV(?:ISION|ISED)?|COND(?:O|MINIUM)?|PAR(?:T)?|PT|AREA|FINAL|FN(?:L)?|PL(?:A|N)?|AMEN(?:D|DMENT)?|TW(?:P)?|TOWNSHIP|OUTL(?:INE)?|NO|PD)S?\b(\s*(\d+|ONE|TWO|THREE|FOUR|FIVE|SIX|SEVEN|EIGHT|NINE|TEN))|\b(?:LT|LOT|BL(?:CK|K|OCK)|PH(?:ASE)?|AD(?:D|DITION|DN|DT)?|PA(?:R|RCEL)?|SEC(?:T|TION)?|TR(?:A|C|T)?|REV(?:ISION|ISED)?|COND(?:O|MINIUM)?|PAR(?:T)?|PT|AREA|FINAL|FN(?:L)?|PL(?:A|N)?|AMEN(?:D|DMENT)?|TW(?:P)?|TOWNSHIP|OUTL(?:INE)?|NO|PD)S?\b
    NO_MATCH = _FME_NO_OP_
    REGEXP = YES
    REPLACE_TEXT = ZZZ
    SRC_ATTRS = _SubdName
    -> Roman_Numerals

Bookmark: Standardize roman numerals that are between spaces
Note: For I-1, an exemption is made to make sure that legitimate names like I-40 are not changed. Also added an exception for examples like X-L (extra large)
Roman_Numerals: Tester
    BOOL_OP = COMPOSITE
    COMPOSITE_TEST = 1 AND  NOT ( 2 OR 3 )
    TEST_CLAUSE:
      CASE_INSENSITIVE_TEST @Value(_SubdName) CONTAINS_REGEX \b(I|I(I)+|IV|V|V(I)+|IX|X)\b
      CASE_INSENSITIVE_TEST @Value(_SubdName) CONTAINS_REGEX I-(40|240|55|69)
      CASE_INSENSITIVE_TEST @Value(_SubdName) CONTAINS_REGEX X-L
    TEST_MODE = CASE_INSENSITIVE_TEST
    PASSED -> _I_
    FAILED -> Junction_4
_I_: StringReplacer
    CASE = NO
    FIND_TEXT = \bI\b
    NO_MATCH = _FME_NO_OP_
    REGEXP = YES
    REPLACE_TEXT = 1
    SRC_ATTRS = _SubdName
    -> _II_
_II_: StringReplacer
    CASE = NO
    FIND_TEXT = \bII\b
    NO_MATCH = _FME_NO_OP_
    REGEXP = YES
    REPLACE_TEXT = 2
    SRC_ATTRS = _SubdName
    -> _III_
_III_: StringReplacer
    CASE = NO
    FIND_TEXT = \bIII\b
    NO_MATCH = _FME_NO_OP_
    REGEXP = YES
    REPLACE_TEXT = 3
    SRC_ATTRS = _SubdName
    -> _IV_
_IV_: StringReplacer
    CASE = NO
    FIND_TEXT = \bIV\b
    NO_MATCH = _FME_NO_OP_
    REGEXP = YES
    REPLACE_TEXT = 4
    SRC_ATTRS = _SubdName
    -> _V_
_V_: StringReplacer
    CASE = NO
    FIND_TEXT = \bV\b
    NO_MATCH = _FME_NO_OP_
    REGEXP = YES
    REPLACE_TEXT = 5
    SRC_ATTRS = _SubdName
    -> _VI_
_VI_: StringReplacer
    CASE = NO
    FIND_TEXT = \bVI\b
    NO_MATCH = _FME_NO_OP_
    REGEXP = YES
    REPLACE_TEXT = 6
    SRC_ATTRS = _SubdName
    -> _VII_
_VII_: StringReplacer
    CASE = NO
    FIND_TEXT = \bVII\b
    NO_MATCH = _FME_NO_OP_
    REGEXP = YES
    REPLACE_TEXT = 7
    SRC_ATTRS = _SubdName
    -> _VIII_
_VIII_: StringReplacer
    CASE = NO
    FIND_TEXT = \bVIII\b
    NO_MATCH = _FME_NO_OP_
    REGEXP = YES
    REPLACE_TEXT = 8
    SRC_ATTRS = _SubdName
    -> _IX_
_IX_: StringReplacer
    CASE = NO
    FIND_TEXT = \bIX\b
    NO_MATCH = _FME_NO_OP_
    REGEXP = YES
    REPLACE_TEXT = 9
    SRC_ATTRS = _SubdName
    -> _X_
_X_: StringReplacer
    CASE = NO
    FIND_TEXT = \bX\b
    NO_MATCH = _FME_NO_OP_
    REGEXP = YES
    REPLACE_TEXT = 10
    SRC_ATTRS = _SubdName
    -> Junction_5
Junction_4
    -> Junction_5
Junction_5
    -> Check_Again_3

Bookmark: Remove Extra Spaces for _SubdName
Note: Then check to see if any more spaces are found
Check_Again_3: Tester
    BOOL_OP = OR
    TEST_CLAUSE = CASE_INSENSITIVE_TEST @Value(_SubdName) CONTAINS_REGEX
    TEST_MODE = CASE_INSENSITIVE_TEST
    PASSED -> Clean_Spaces_3
    FAILED -> Junction_3
Clean_Spaces_3: StringReplacer
    CASE = NO
    FIND_TEXT = "  "
    NO_MATCH = _FME_NO_OP_
    REGEXP = NO
    REPLACE_TEXT = " "
    SRC_ATTRS = _SubdName
    -> trim_end_spaces
Note: Replace double spaces with single spaces. Trim ends as well
trim_end_spaces: AttributeTrimmer
    SRC_ATTRS = _ParcelID,_SubdName
    TRIM_CHARS = " "
    TRIM_TO_NONE = Yes
    TRIM_TYPE = BOTH
    -> Junction_32
Junction_3
    -> Junction_32

FME custom transformer Title Case

Parameters:
- _SUBDNAME = @Value(_SubdName)   # Subdname
- FME_PROCESS_GROUP_BY =   # "" Group By
- FME_PROCESS_GROUPS_ORDERED = No   # When All Features Received,No%When Group Changes (Advanced),Yes Complete Groups

Input (input)
    -> Change_to_Title
Note: Change _SubdName to Full Title Case
Change_to_Title: StringCaseChanger
    ATTRCHOICE_ACTION = SELECTED
    ATTRLIST = _SubdName
    CHANGE_TYPE_CASE = fulltitle
    ATTRCHOICE = Selected Attributes
    CHANGE_TYPE = Full Title Case
    -> Find_MC
Note: Note: this is not by any means an exhaustive list of exceptions. Add more as needed
Output (output)

Bookmark: Mc Scenarios
Note: Do a regex search for MC[A-Z] to find examples like McFarlin
Note: If not found, continue...
Find_MC: Tester
    BOOL_OP = OR
    TEST_CLAUSE = CASE_INSENSITIVE_TEST @Value(_SubdName) CONTAINS_REGEX MC[A-Z]
    TEST_MODE = CASE_INSENSITIVE_TEST
    PASSED -> Replace_Mc
    FAILED -> Junction
Note: Replace Mc with ~~~ / This is done because those characters are guaranteed to not be used legitimately in the data. This way we can find these later and replace them with Mc again
Replace_Mc: StringReplacer
    CASE = NO
    FIND_TEXT = Mc
    NO_MATCH = _FME_NO_OP_
    REGEXP = NO
    REPLACE_TEXT = ~~~
    SRC_ATTRS = _SubdName
    -> Split_Title_Case
Note: Change to newly split strings to title case
Split_Title_Case: StringCaseChanger
    ATTRCHOICE_ACTION = SELECTED
    ATTRLIST = _SubdName
    CHANGE_TYPE_CASE = fulltitle
    ATTRCHOICE = Selected Attributes
    CHANGE_TYPE = Full Title Case
    -> Replace_wth_Mc
Note: Replace ~~~ with Mc again
Replace_wth_Mc: StringReplacer
    CASE = NO
    FIND_TEXT = ~~~
    NO_MATCH = _FME_NO_OP_
    REGEXP = NO
    REPLACE_TEXT = Mc
    SRC_ATTRS = _SubdName
    -> MixedCase_Exceptions
Junction
    -> MixedCase_Exceptions

Bookmark: Notable Exceptions
Note: Search for each individually
MixedCase_Exceptions: TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(_SubdName) CONTAINS_REGEX YMCA",YMCA,"BOOL_OP,OR,COMPOSITE_TEST,""""""1"""""",TEST_CLAUSE,CASE_INSENSITIVE_TEST @Value(_SubdName) CONTAINS_REGEX (^USA | USA | USA$)",USA,"BOOL_OP,OR,COMPOSITE_TEST,""""""1"""""",TEST_CLAUSE,CASE_INSENSITIVE_TEST @Value(_SubdName) CONTAINS_REGEX (^TN | TN | TN$)",TN
    YMCA -> YMCA
    USA -> USA
    TN -> TN
    <UNFILTERED> -> Output (output)
Note: Then replace with the exception
YMCA: StringReplacer
    CASE = NO
    FIND_TEXT = YMCA
    NO_MATCH = _FME_NO_OP_
    REGEXP = YES
    REPLACE_TEXT = YMCA
    SRC_ATTRS = _SubdName
    -> Junction_2
USA: StringReplacer
    CASE = NO
    FIND_TEXT = (^USA | USA | USA$)
    NO_MATCH = _FME_NO_OP_
    REGEXP = YES
    REPLACE_TEXT = USA
    SRC_ATTRS = _SubdName
    -> Junction_2
TN: StringReplacer
    CASE = NO
    FIND_TEXT = (^TN | TN | TN$)
    NO_MATCH = _FME_NO_OP_
    REGEXP = YES
    REPLACE_TEXT = TN
    SRC_ATTRS = _SubdName
    -> Junction_2
Junction_2
    -> Output (output)
